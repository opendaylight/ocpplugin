module ocp-provider {
    yang-version 1;
    namespace "urn:opendaylight:params:xml:ns:yang:ocp:api";
    prefix "ocpplugin-cfg";

    import config { prefix config; revision-date 2013-04-05; }

    description
        "ocp-plugin-custom-config";

    revision "2015-08-11" {
        description
            "Initial revision";
    }

    identity ocp-provider{
        base config:service-type;
        config:java-class "org.opendaylight.ocpplugin.api.ocp.OcpPluginProvider";
    }
}
