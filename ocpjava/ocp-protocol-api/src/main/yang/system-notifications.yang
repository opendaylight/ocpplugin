/*
 * Copyright (c) 2015 Foxconn Corporation and others.  All rights reserved.
 *
 * This program and the accompanying materials are made available under the
 * terms of the Eclipse Public License v1.0 which accompanies this distribution,
 * and is available at http://www.eclipse.org/legal/epl-v10.html
 */
 
 module system-notifications {
    namespace "urn:opendaylight:ocp:system";
    prefix "ofs";

    organization "Foxconn";
    contact "marko.ch.lai@foxconn.com";
    description "Model of system messages used in OCP Protocol Library";

    revision "2015-08-11" {
      description 
        "Initial revision";
    }

    notification disconnect-event {
        description "Disconnect notification";
        leaf info {
            type string;
        }
    }

    notification radioHead-idle-event {
        description "Radiohead-idle notification";
        leaf info {
            type string;
        }
    }

}
