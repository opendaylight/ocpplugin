/*
 * Copyright (c) 2015 Foxconn Corporation and others.  All rights reserved.
 *
 * This program and the accompanying materials are made available under the
 * terms of the Eclipse Public License v1.0 which accompanies this distribution,
 * and is available at http://www.eclipse.org/legal/epl-v10.html
 */
 
 module ocp-types {
    namespace "urn:opendaylight:ocp:common:types";
    prefix "ocpt";

    import ocp-xsd { prefix ocpx; revision-date 2015-08-11; }
    import ietf-yang-types { prefix yang; }

    organization "Foxconn";
    contact "marko.ch.lai@foxconn.com";
    description "OCP common types";
    
    revision "2015-08-11" {
      description
        "Initial revision";
    }

    grouping ocpHeader {
        reference "ocp_header struct in ORI Spec";
        leaf msgType {
            type OcpMsgType;
            description "OCP message type";
        }
        leaf xid {
            type uint32;
            description "Transaction ID";
        }
    }

    grouping getParamInput {
        leaf objId {
            type ObjId;
        }
        leaf paramName {
            type string;
        }
    }

    grouping getParamOutput {
        list obj {
            key id;
            leaf id {
                type ObjId;
            }
            list param {
                key name;
                leaf name {
                    type string;
                }
                leaf value {
                    type string;
                }
            }
        }
    }

    grouping modifyParamInput {
        leaf objId {
            type ObjId;
        }
        list param {
            key name;
            leaf name {
                type string;
            }
            leaf value {
                type string;
            }
        }
    }

    grouping modifyParamOutput {
        leaf objId {
            type ObjId;
        }
        list param {
            key name;
            leaf name {
                type string;
            }
            leaf result {
                type ModifyParamRes;
            }
        }
    }

    grouping createObjInput {
        leaf objType {
            type ObjType;
        }
        list param {
            key name;
            leaf name {
                type string;
            }
            leaf value {
                type string;
            }
        }
    }

    grouping createObjOutput {
        leaf objId {
            type ObjId;
        }
        list param {
            key name;
            leaf name {
                type string;
            }
            leaf result {
                type CreateObjRes;
            }
        }
    }

    grouping getStateInput {
        leaf objId {
            type ObjId;
        }
        leaf stateType {
            type StateAllType;
        }
        leaf eventDrivenReporting {
            type boolean;
        }
    }

    grouping getStateOutput {
        list obj {
            key id;
            leaf id {
                type ObjId;
            }
            list state {
                key type;
                leaf type {
                    type StateType;
                }
                leaf value {
                    type StateVal;
                }
            }
        }
    }

    grouping modifyStateInput {
        leaf objId {
            type ObjId;
        }
        leaf stateType {
            type StateType;
        }
        leaf stateValue {
            type StateVal;
        }
    }

    grouping modifyStateOutput {
        leaf objId {
            type ObjId;
        }
        leaf stateType {
            type StateType;
        }
        leaf stateValue {
            type StateVal;
        }
    }

    grouping getFaultInput {
        leaf objId {
            type ObjId;
        }
        leaf eventDrivenReporting {
            type boolean;
        }
    }

    grouping getFaultOutput {
        list obj {
            key id;
            leaf id {
                type ObjId;
            }
            list fault {
                key id;
                leaf id {
                    type FaultId;
                }
                leaf severity {
                    type FaultSeverity;
                }
                leaf timestamp{
                    type ocpx:xsd-dateTime;
                }
                leaf descr {
                    type string;
                }
                leaf-list affectedObj {
                    type string;
                }
            }
        }
    }

    grouping stateChangeInd {
        leaf objId {
            type ObjId;
        }
        leaf stateType {
            type StateType;
        }
        leaf stateValue {
            type StateVal;
        }
    }

    grouping faultInd {
        leaf objId {
            type ObjId;
        }
        leaf faultId {
            type FaultId;
        }
        leaf state{
            type FaultState;
        }
        leaf severity {
            type FaultSeverity;
        }
        leaf timestamp{
            type ocpx:xsd-dateTime;
        }
        leaf descr {
            type string;
        }
        leaf-list affectedObj {
            type string;
        }
    }

    typedef OcpMsgType {
        type enumeration {
            enum "HEALTHCHECKREQ";
            enum "HEALTHCHECKRESP";
            enum "SETTIMEREQ";
            enum "SETTIMERESP";
            enum "RESETREQ";
            enum "RESETRESP";
            enum "GETPARAMREQ";
            enum "GETPARAMRESP";
            enum "MODIFYPARAMREQ";
            enum "MODIFYPARAMRESP";
            enum "CREATEOBJREQ";
            enum "CREATEOBJRESP";
            enum "DELETEOBJREQ";
            enum "DELETEOBJRESP";
            enum "GETSTATEREQ";
            enum "GETSTATERESP";
            enum "STATECHANGEIND";
            enum "MODIFYSTATEREQ";
            enum "MODIFYSTATERESP";
            enum "GETFAULTREQ";
            enum "GETFAULTRESP";
            enum "FAULTIND";
            enum "HELLOACK";
            enum "HELLOIND";
            enum "REDIRECTREQ";
            enum "REDIRECTRESP";
            //enum "ERR";

        }
    }

    typedef ObjId {
        type string {
            pattern '([a-z,A-Z,_][a-z,A-Z,0-9,_]*:[0-9][0-9]*([\/][a-z,A-Z,_][a-z,A-Z,0-9,_]*:[0-9][0-9]*)*)|ALL';
        }
    }

    typedef ObjType {
        type string {
            pattern '[a-z,A-Z,_][a-z,A-Z,0-9,_]*';
        }
    }

    typedef OriRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";

            enum "FAIL_INVALID_TIMEDATA";
        }
    }

    typedef HealthCheckRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";
        }
    }

    typedef SetTimeRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";

            enum "FAIL_INVALID_TIMEDATA";
        }
    }

    typedef ReResetRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";
        }
    }

    typedef GetParamRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";

            enum "FAIL_UNKNOWN_OBJECT";
            enum "FAIL_UNKNOWN_PARAM";
        }
    }

    typedef ModifyParamGlobRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";

            enum "FAIL_UNKNOWN_OBJECT";
            enum "FAIL_PARAMETER_FAIL";
            enum "FAIL_NOSUCH_RESOURCE";
        }
    }

    typedef ModifyParamRes {
        type enumeration {
            enum "SUCCESS";
            enum "FAIL_UNKNOWN_PARAM";
            enum "FAIL_PARAM_READONLY";
            enum "FAIL_PARAM_LOCKREQUIRED";
            enum "FAIL_VALUE_OUTOF_RANGE";
            enum "FAIL_VALUE_TYPE_ERROR";
        }
    }

    typedef CreateObjRes {
        type enumeration {
            enum "SUCCESS";
            enum "FAIL_UNKNOWN_PARAM";
            enum "FAIL_PARAM_READONLY";
            enum "FAIL_PARAM_LOCKREQUIRED";
            enum "FAIL_VALUE_OUTOF_RANGE";
            enum "FAIL_VALUE_TYPE_ERROR";
        }
    }

    typedef CreateObjGlobRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";

            enum "FAIL_UNKNOWN_OBJTYPE";
            enum "FAIL_STATIC_OBJTYPE";
            enum "FAIL_UNKNOWN_OBJECT";
            enum "FAIL_CHILD_NOTALLOWED";
            enum "FAIL_OUTOF_RESOURCES";
            enum "FAIL_PARAMETER_FAIL";
            enum "FAIL_NOSUCH_RESOURCE";
        }
    }

    typedef DeleteObjRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";

            enum "FAIL_UNKNOWN_OBJECT";
            enum "FAIL_STATIC_OBJTYPE";
            enum "FAIL_LOCKREQUIRED";
        }
    }

    typedef StateType {
        type enumeration {
            enum "AST";
            enum "FST";
        }
    }

    typedef StateAllType {
        type enumeration {
            enum "AST";
            enum "FST";
            enum "ALL";
        }
    }

    typedef StateVal {
        type enumeration {
            //AST
            enum "LOCKED";
            enum "UNLOCKED";
            //FST
            enum "PRE_OPERATIONAL";
            enum "OPERATIONAL";
            enum "DEGRADED";
            enum "FAILED";
            enum "NOT_OPERATIONAL";
            enum "DISABLED";
        }
    }

    typedef GetStateRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";

            enum "FAIL_UNKNOWN_OBJECT";
            enum "FAIL_UNKNOWN_STATETYPE";
            enum "FAIL_VALUE_OUTOF_RANGE";
        }
    }

    typedef ModifyStateRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";

            enum "FAIL_UNKNOWN_OBJECT";
            enum "FAIL_UNKNOWN_STATETYPE";
            enum "FAIL_UNKNOWN_STATEVALUE";
            enum "FAIL_STATE_READONLY";
            enum "FAIL_RESOURCE_UNAVAILABLE";
            enum "FAIL_RESOURCE_INUSE";
            enum "FAIL_PARENT_CHILD_CONFLICT";
            enum "FAIL_PRECONDITION_NOTMET";
        }
    }

    typedef FaultId {
        type enumeration {
            enum "FAULT_EXT_SUPPLY_UNDERVOLT";
            enum "FAULT_RE_OVERTEMP";
            enum "FAULT_DIG_IN_OVERDRIVE";
            enum "FAULT_RF_OUT_OVERDRIVE";
            enum "FAULT_TX_GAIN_FAIL";
            enum "FAULT_RX_GAIN_FAIL";
            enum "FAULT_VSWR_OUTOF_RANGE";
            enum "FAULT_NON_AISG_TMA_MALFCT";
            enum "FAULT_LINK_FAIL";
            enum "FAULT_ORI_PORT_FAIL";
            enum "FAULT_ORI_SYNC_FAIL";
            enum "FAULT_AISG_MALFCT";
        }
    }
    
    typedef FaultState {
        type enumeration {
            enum "ACTIVE";
            enum "CLEARED";
        }
    }

    typedef FaultSeverity {
        type enumeration {
            enum "FAILED";
            enum "DEGRADED";
            enum "WARNING";
        }
    }

    typedef GetFaultRes {
        type enumeration {
            enum "SUCCESS";
            enum "FAIL_SYNTAX_ERROR";
            enum "FAIL_UNRECOGNIZED_MESSAGE";
            enum "FAIL_RE_BUSY";
            enum "FAIL_MISSING_PARAMETER";
            enum "FAIL_PARAMETER_ERROR";

            enum "FAIL_UNKNOWN_OBJECT";
            enum "FAIL_VALUE_OUTOF_RANGE";
        }
    }
}
