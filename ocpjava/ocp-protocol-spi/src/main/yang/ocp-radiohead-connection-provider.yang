/*
 * Copyright (c) 2015 Foxconn Corporation and others.  All rights reserved.
 *
 * This program and the accompanying materials are made available under the
 * terms of the Eclipse Public License v1.0 which accompanies this distribution,
 * and is available at http://www.eclipse.org/legal/epl-v10.html
 */

module ocp-radiohead-connection-provider {
	yang-version 1;
    namespace "urn:opendaylight:params:xml:ns:yang:ocp:radiohead:connection:provider";
    prefix "ocp-radiohead-connection-provider";

    import config {prefix config; revision-date 2013-04-05; }

    description
        "ocp-radiohead-connection-provider service definitions";

    revision "2015-08-11" {
        description
            "Initial revision";
    }

    identity ocp-radiohead-connection-provider {
         base "config:service-type";
         config:java-class "org.opendaylight.ocpjava.protocol.spi.connection.RadioHeadConnectionProvider";
    }

    identity ocp-statistics-collection-service {
        description
            "OcpStatisticsHandlerService interface as a OcpStatisticsCollection interface identity";
        base config:service-type;
        config:java-class "org.opendaylight.ocpjava.protocol.spi.statistics.OcpStatisticsHandler";
    }
}
