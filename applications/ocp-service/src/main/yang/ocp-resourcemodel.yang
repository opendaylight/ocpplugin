module ocp-resourcemodel {

    yang-version 1;
    namespace "urn:opendaylight:params:xml:ns:yang:ocp:applications:ocp-resourcemodel";
    prefix "ocp-resourcemodel";

    import ocp-types { prefix ocpt; }
    import ietf-yang-types { prefix yang; revision-date 2013-07-15;}
    import ietf-inet-types { prefix inet; }
    import opendaylight-inventory { prefix inv; revision-date "2013-08-19";}
    import ocp-xsd { prefix ocpx; revision-date "2015-08-11"; }
    
    description "OCP Resource Model";    

    revision "2015-08-11" {
      description
        "Initial revision.";
    }
    container resourceModel {
        config false;
        list RadioHead {
            key nodeId;
            leaf ipAddr {
                type inet:ipv4-address;                
            }
            leaf nodeId {
                type inv:node-id;                
            }
            container re{
                leaf vendorID {
                    type string{
                        length 3;
                    }                    
                }
                leaf productID {
                    type string{
                        length "0..80";
                    }                    
                }
                leaf productRev {
                    type string{
                        length "0..80";
                    }                    
                }
                leaf serialNumber {
                    type string{
                        length "0..40";
                    }                    
                }
                leaf protocolVer {
                    type string{
                        length "0..10";
                    }                    
                }
                leaf agcTargetLevCfgGran {
                    type enumeration {
                        enum "RX_SIG_PATH";
                        enum "RE";
                    }                    
                }
                leaf agcSettlTimeCfgGran {
                    type enumeration {
                        enum "RX_SIG_PATH";
                        enum "RE";
                    }                    
                }
                leaf agcSettlTimeCap {
                    type string {
                            pattern '([0-9a-fA-F]{2}(:[0-9a-fA-F]{2})*)?';
                            length "4";
                    }                    
                }
            }
            
            list antPort {
                key id;
                leaf id {
                    type ocpx:xsd-unsignedInt;                    
                }
                description "This is the name provided to the Physical Antenna Port by the RE vendor, as indicated on the RE housing";
                leaf portLabel {
                    type string{
                        length "0..80";
                    }                    
                }
            }
            
            list TxSigPath_UTRAFDD {
                key id;
                leaf id {
                    type ocpx:xsd-unsignedInt;                                        
                }
                leaf dlCalRFMax {
                    description "Max possible buffer in RE for DL timing calibration";
                    type ocpx:xsd-unsignedShort {
                        range "16..8191";
                    }                    
                }
                leaf t2a {
                    description "Time delay";
                    type ocpx:xsd-unsignedInt {
                        range "0..66667";
                    }                    
                }
                leaf dlCalRF {
                    description "Time delay value to enable DL timing delay calibration";
                    type ocpx:xsd-unsignedShort {
                        range "0..65535";
                    }                                        
                }
                leaf maxTxPwr {
                    description "Max Transmission Power";
                    type ocpx:xsd-unsignedShort {
                        range "0..500";
                    }                                        
                }
                leaf axcW {
                    description "AxC container group start position parameter(W)";
                    type ocpx:xsd-unsignedByte {
                        range "1..15";
                    }                                        
                }
                leaf axcB {
                    description "AxC container group start position parameter(B)";
                    type ocpx:xsd-unsignedByte {
                        range "0..255";
                    }                                        
                }
                leaf oriLink {
                    description "The ORI Link on which the required AxC container group is mapped";
                    type ocpt:ObjId;                                        
                }
                leaf uarfcn {
                    description "The downlink UARFCN of the UTRA carrier";
                    type ocpx:xsd-unsignedShort {
                        range "0..16383";
                    }                                        
                }
                leaf antPort {
                    description "Reference to antenna port object representing the antenna port through which the RF signal of this TxSigPath shall be transmitted.";
                    type ocpt:ObjId;                                        
                }
            }

            list TxSigPath_EUTRAFDD {
                key id;
                leaf id {
                    type ocpx:xsd-unsignedInt;                                        
                }
                leaf chanBW {
                    description "E-UTRA Channel Bandwidth of the E-UTRA carrier";
                    type ocpx:xsd-unsignedShort {
                        range "0..500";
                    }                                        
                }
                leaf dlCalREMax {
                    description "Max possible buffer in RE for DL timing calibration expressed in TC/16 (minimum value 1*Tc)";
                    type ocpx:xsd-unsignedShort {
                        range "0..500";
                    }                    
                }
                leaf t2a {
                    description "Time delay";
                    type ocpx:xsd-unsignedInt {
                        range "0..66667";
                    }                    
                }
                leaf dlCalRE {
                    description "Time delay value to enable DL timing delay calibration expressed in TC/16";
                    type ocpx:xsd-unsignedShort;                                        
                }
                leaf maxTxPwr {
                    description "Max Transmission Power";
                    type ocpx:xsd-unsignedShort {
                        range "0..500";
                    }                                        
                }
                leaf axcW {
                    description "AxC container group start position parameter(W)";
                    type ocpx:xsd-unsignedByte {
                        range "1..15";
                    }                                       
                }
                leaf axcB {
                    description "AxC container group start position parameter(B)";
                    type ocpx:xsd-unsignedByte {
                        range "0..255";
                    }                                        
                }
                leaf oriLink {
                    description "The ORI Link on which the required AxC container group is mapped";
                    type ocpt:ObjId;                                        
                }
                leaf earfcn {
                    description "The downlink EARFCN of the E-UTRA carrier";
                    type ocpx:xsd-unsignedShort {
                        range "0..65535";
                    }                                        
                }         
                leaf antPort {
                    description "Reference to antenna port object representing the antenna port through which the RF signal of this TxSigPath shall be transmitted.";
                    type ocpt:ObjId;                                        
                }        
                leaf enableIQDLComp {
                    description "Downlink IQ Compression Enable";
                    type boolean;                                        
                }  
                leaf sigmaIQ {
                    description "Sigma_IQ";
                    type ocpx:xsd-unsignedShort {
                        range "1..65535";
                    }                                      
                }  
            }
            
            list TxSigPath_EUTRATDD {
                key id;
                leaf id {
                    type ocpx:xsd-unsignedInt;                                        
                }
                leaf chanBW {
                    description "E-UTRA Channel Bandwidth";
                    type ocpx:xsd-unsignedShort {
                        range "0..500";
                    }                                        
                }
                leaf tddULDLConfig {
                    description "TDD uplink/downlink configuration";
                    type ocpx:xsd-unsignedByte {
                        range "0..255";
                    }                                        
                }
                leaf tddSpecialSFConfig {
                    description "E-UTRA Channel Bandwidth";
                    type ocpx:xsd-unsignedByte {
                        range "0..255";
                    }                                        
                }
                leaf tddCPLengthDL {
                    type enumeration {
                        enum "Normal";
                        enum "Extended";
                    }                                        
                }
                leaf dlCalREMax {
                    description "Max possible buffer in RE for DL timing calibration";
                    type ocpx:xsd-unsignedShort {
                        range "16..8191";
                    }                    
                }
                leaf t2a {
                    description "Time delay";
                    type ocpx:xsd-unsignedInt {
                        range "0..66667";
                    }                    
                }
                leaf dlCalRE {
                    description "Time delay value to enable DL timing delay calibration";
                    type ocpx:xsd-unsignedShort {
                        range "0..65535";
                    }                                        
                }
                leaf maxTxPwr {
                    description "Max Transmission Power";
                    type ocpx:xsd-unsignedShort {
                        range "0..500";
                    }                                        
                }
                leaf axcW {
                    description "AxC container group start position parameter(W)";
                    type ocpx:xsd-unsignedByte {
                        range "1..15";
                    }                                        
                }
                leaf axcB {
                    description "AxC container group start position parameter(B)";
                    type ocpx:xsd-unsignedByte {
                        range "0..255";
                    }                                        
                }
                leaf oriLink {
                    description "The ORI Link on which the required AxC container group is mapped";
                    type ocpt:ObjId;                                        
                }
                leaf earfcn {
                    description "The downlink EARFCN of the E-UTRA carrier";
                    type ocpx:xsd-unsignedShort {
                        range "0..65535";
                    }                                        
                }         
                leaf antPort {
                    description "Reference to antenna port object representing the antenna port through which the RF signal of this TxSigPath shall be transmitted.";
                    type ocpt:ObjId;                                        
                }
                leaf enableIQDLComp {
                    description "Downlink IQ Compression Enable";
                    type boolean;                                        
                }  
                leaf sigmaIQ {
                    description "Sigma_IQ";
                    type ocpx:xsd-unsignedShort {
                        range "1..65535";
                    }                                        
                }                          
            }
                
            list TxSigPath_GSM {
                key id;
                leaf id {
                    type ocpx:xsd-unsignedInt;                                        
                }
                leaf dlCalREMax {
                    description "Max possible buffer in RE for DL timing calibration";
                    type ocpx:xsd-unsignedShort {
                        range "16..8191";
                    }                    
                }
                leaf freqBandInd {
                    description "Frequency band indicator";
                    type enumeration {
                        enum "GSM850";
                        enum "P-GSM900";
                        enum "DCS1800";
                        enum "PCS1900";
                    }                 
                }
                leaf t2a {
                    description "Time delay";
                    type ocpx:xsd-unsignedInt {
                        range "0..66667";
                    }                    
                }
                leaf dlCalRE {
                    description "Time delay value to enable DL timing delay calibration";
                    type ocpx:xsd-unsignedShort {
                        range "0..65535";
                    }
                }
                leaf maxTxPwr {
                    description "Max Transmission Power";
                    type ocpx:xsd-unsignedShort {
                        range "0..500";
                    }
                }
                leaf axcW {
                    description "AxC container group start position parameter(W)";
                    type ocpx:xsd-unsignedByte {
                        range "1..15";
                    }
                }
                leaf axcB {
                    description "AxC container group start position parameter(B)";
                    type ocpx:xsd-unsignedByte {
                        range "0..255";
                    }
                }
                leaf oriLink {
                    description "The ORI Link on which the required AxC container group is mapped";
                    type ocpt:ObjId;
                }
                leaf antPort {
                    description "Reference to antenna port object representing the antenna port through which the RF signal of this TxSigPath shall be transmitted.";
                    type ocpt:ObjId;
                }        
            }

            list RxSigPath_UTRAFDD {
                key id;
                leaf id {
                    type ocpx:xsd-unsignedInt;
                }
                leaf ulCalREMax {
                    description "Max possible buffer in RE for UL timing calibration";
                    type ocpx:xsd-unsignedShort {
                        range "2..1023";
                    }                    
                }
                leaf ta3 {
                    description "Time delay";
                    type ocpx:xsd-unsignedInt {
                        range "0..66667";
                    }                    
                }
                leaf ulCalRE {
                    description "Time delay value to enable UL timing delay calibration";
                    type ocpx:xsd-unsignedShort {
                        range "0..65535";
                    }
                }
                leaf axcW {
                    description "AxC container group start position parameter(W)";
                    type ocpx:xsd-unsignedByte {
                        range "1..15";
                    }
                }
                leaf axcB {
                    description "AxC container group start position parameter(B)";
                    type ocpx:xsd-unsignedByte {
                        range "0..255";
                    }
                }
                leaf rtwpGroup {
                    description "Identifies location of the RTWP measurement value for this AxC within the RTWP control word";
                    type ocpx:xsd-unsignedByte {
                        range "1..64";
                    }
                }
                leaf oriLink {
                    description "The ORI Link on which the required AxC container group is mapped";
                    type ocpt:ObjId;
                }
                leaf antPort {
                    description "Reference to Physical Antenna Port object representing the antenna port from which the RF signal of this RxSigPath shall be received.";
                    type ocpt:ObjId;
                }
                leaf uarfcn {
                    description "The uplink UARFCN of the UTRA carrier";
                    type ocpx:xsd-unsignedShort {
                        range "0..16383";
                    }
                }
                leaf ulFeedAdj {
                    description "Uplink Feeder Adjustment";
                    type ocpx:xsd-short {
                        range "-500..500";
                    }
                }
                leaf ulTgtRMSLvl {
                    description "Uplink AGC Target RMS Level";
                    type ocpx:xsd-unsignedByte {
                        range "6..32";
                    }
                }
                leaf ulAGCSetlgTime {
                    description "Uplink AGC settling time";
                    type ocpx:xsd-unsignedByte {
                        range "0..12";
                    }
                } 
            }

            list RxSigPath_EUTRAFDD {
                key id;
                leaf id {
                    type ocpx:xsd-unsignedInt;
                }
                leaf chanBW {
                    description "E-UTRA Channel Bandwidth";
                    type ocpx:xsd-unsignedShort {
                        range "0..500";
                    }
                }
                leaf ulCalREMax {
                    description "Max possible buffer in RE for UL timing calibration";
                    type ocpx:xsd-unsignedShort {
                        range "2..1023";
                    }                    
                }
                leaf ta3 {
                    description "Time delay";
                    type ocpx:xsd-unsignedInt {
                        range "0..66667";
                    }                    
                }
                leaf ulCalRE {
                    description "Time delay value to enable UL timing delay calibration";
                    type ocpx:xsd-unsignedShort {
                        range "0..65535";
                    }
                }
                leaf axcW {
                    description "AxC container group start position parameter(W)";
                    type ocpx:xsd-unsignedByte {
                        range "1..15";
                    }
                }
                leaf axcB {
                    description "AxC container group start position parameter(B)";
                    type ocpx:xsd-unsignedByte {
                        range "0..255";
                    }
                }
                leaf oriLink {
                    description "The ORI Link on which the required AxC container group is mapped";
                    type ocpt:ObjId;
                }
                leaf antPort {
                    description "Reference to Physical Antenna Port object representing the antenna port from which the RF signal of this RxSigPath shall be received.";
                    type ocpt:ObjId;
                }
                leaf earfcn {
                    description "The uplink EARFCN of the E-UTRA carrier";
                    type ocpx:xsd-unsignedShort {
                        range "0..65535";
                    }
                }         
                leaf enableIQDLComp {
                    description "Uplink IQ Compression Enable";
                    type boolean;
                }  
                leaf sigmaIQ {
                    description "Sigma_IQ";
                    type ocpx:xsd-unsignedShort {
                        range "1..65535";
                    }
                }  
            }

            list RxSigPath_EUTRATDD {
                key id;
                leaf id {
                    type ocpx:xsd-unsignedInt;
                }
                leaf chanBW {
                    description "E-UTRA Channel Bandwidth";
                    type ocpx:xsd-unsignedShort {
                        range "0..500";
                    }
                }
                leaf tddULDLConfig {
                    description "The uplink/downlink physical layer configuration for TDD mode.";
                    type ocpx:xsd-unsignedShort {
                        range "0..255";
                    }
                }
                leaf tddSpecialSFConfig {
                    description "The special subframe configuration for TDD mode";
                    type ocpx:xsd-unsignedShort {
                        range "0..255";
                    }
                }
                leaf tddCPLengthUL {
                    description "The uplink Cyclic Prefix Length for TDD mode";
                    type enumeration {
                        enum "Normal";
                        enum "Extended";
                    }
                }
                leaf ulCalREMax {
                    description "Max possible buffer in RE for UL timing calibration";
                    type ocpx:xsd-unsignedShort {
                        range "2..1023";
                    }                    
                }
                leaf ta3 {
                    description "Time delay";
                    type ocpx:xsd-unsignedInt {
                        range "0..66667";
                    }                    
                }
                leaf ulCalRE {
                    description "Time delay value to enable UL timing delay calibration";
                    type ocpx:xsd-unsignedShort {
                        range "0..65535";
                    }
                }
                leaf axcW {
                    description "AxC container group start position parameter(W)";
                    type ocpx:xsd-unsignedByte {
                        range "1..15";
                    }
                }
                leaf axcB {
                    description "AxC container group start position parameter(B)";
                    type ocpx:xsd-unsignedByte {
                        range "0..255";
                    }
                }
                leaf oriLink {
                    description "The ORI Link on which the required AxC container group is mapped";
                    type ocpt:ObjId;
                }
                leaf antPort {
                    description "Reference to Physical Antenna Port object representing the antenna port from which the RF signal of this RxSigPath shall be received.";
                    type ocpt:ObjId;
                }
                leaf earfcn {
                    description "The uplink EARFCN of the E-UTRA carrier";
                    type ocpx:xsd-unsignedShort {
                        range "0..65535";
                    }
                }         
                leaf enableIQDLComp {
                    description "Uplink IQ Compression Enable";
                    type boolean;
                }  
                leaf sigmaIQ {
                    description "Sigma_IQ";
                    type ocpx:xsd-unsignedShort {
                        range "1..65535";
                    }
                } 
            }

            list RxSigPath_GSM {
                key id;
                leaf id {
                    type ocpx:xsd-unsignedInt;
                }
                leaf ulCalREMax {
                    description "Max possible buffer in RE for UL timing calibration";
                    type ocpx:xsd-unsignedShort {
                        range "2..1023";
                    }                    
                }
                leaf freqBandInd {
                    description "Frequency band indicator";
                    type enumeration {
                        enum "GSM850";
                        enum "P-GSM900";
                        enum "DCS1800";
                        enum "PCS1900";
                    }                 
                }
                leaf ta3 {
                    description "Time delay";
                    type ocpx:xsd-unsignedInt {
                        range "0..66667";
                    }                    
                }
                leaf ulCalRE {
                    description "Time delay value to enable UL timing delay calibration";
                    type ocpx:xsd-unsignedShort {
                        range "0..65535";
                    }
                }
                leaf axcW {
                    description "AxC container group start position parameter(W)";
                    type ocpx:xsd-unsignedByte {
                        range "1..15";
                    }
                }
                leaf axcB {
                    description "AxC container group start position parameter(B)";
                    type ocpx:xsd-unsignedByte {
                        range "0..255";
                    }
                }
                leaf oriLink {
                    description "The ORI Link on which the required AxC container group is mapped";
                    type ocpt:ObjId;
                }
                leaf antPort {
                    description "Reference to antenna port object representing the antenna port through which the RF signal of this TxSigPath shall be transmitted.";
                    type ocpt:ObjId;
                }  
                leaf ulFeedAdj {
                    description "Uplink Feeder Adjustment";
                    type ocpx:xsd-short {
                        range "-500..500";
                    }
                }
            }

            list aisgPort {
                key id;
                leaf id {
                    type ocpx:xsd-unsignedInt;
                }
                leaf portLabel {
                    type string{
                        length "0..80";
                    }                    
                }
                leaf busPowerEnable {
                    description "Controls the output power of the AISG port";
                    type boolean;
                }
                list aisgALD {
                    key id;
                    leaf id {
                        type ocpx:xsd-unsignedInt;
                    }
                    leaf deviceType {
                        type ocpx:xsd-unsignedByte;
                    }
                    leaf UID {
                        type string;
                    }
                    leaf releaseID {
                        type ocpx:xsd-unsignedByte {
                            range "0..255";
                        }                    
                    }
                    leaf aisgVersion {
                        type ocpx:xsd-unsignedByte {
                            range "0..255";
                        }                    
                    }
                    leaf deviceTypeVersion {
                        type string;                    
                    }		                
                    leaf frameLength {
                        type ocpx:xsd-unsignedShort {
                            range "74..max";
                        }                    
                    } 
                    leaf hdlcAddress {
                        type ocpx:xsd-unsignedByte;                    
                    }
                }
            }
        }
        
    } // container resourceModel
}
