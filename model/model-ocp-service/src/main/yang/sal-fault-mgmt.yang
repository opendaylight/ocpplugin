module sal-fault-mgmt {

    yang-version 1;
    namespace "urn:opendaylight:ocp:fault:mgmt";
    prefix fault-mgmt;

    import ocp-types { prefix ocpt; }
    import ietf-yang-types { prefix yang; }
    import ietf-inet-types { prefix inet; }
    import opendaylight-inventory { prefix inv; revision-date "2013-08-19"; }

    description "OCP elementary functions - fault management";

    revision "2015-08-11" {
      description
        "Initial revision.";
    }


    rpc get-fault {
        input {
            uses inv:node-context-ref;
            uses ocpt:getFaultInput;
        }
        output {
            leaf result {
                type ocpt:GetFaultRes;
            }
            uses ocpt:getFaultOutput; 
        }
    } // rpc get-fault


    notification fault-ind {
        uses inv:node-context-ref;
        uses ocpt:faultInd;
    }

}
