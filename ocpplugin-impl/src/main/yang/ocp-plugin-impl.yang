module ocp-plugin-provider-impl {
    yang-version 1;
    namespace "urn:opendaylight:params:xml:ns:yang:config:ocp:plugin:impl";
    prefix "ocp-plugin-provider-impl";

    import config {prefix config; revision-date 2013-04-05;}
    import rpc-context {prefix rpcx; revision-date 2013-06-17;}
    import ocp-provider {prefix ocp-provider; revision-date 2015-08-11;}
    import ocp-radiohead-connection-provider {prefix ocp-radiohead-connection-provider; revision-date 2015-08-11;}
    import opendaylight-md-sal-binding {prefix md-sal-binding; revision-date 2013-10-28;}
    import opendaylight-sal-binding-broker-impl {prefix sal-broker; revision-date 2013-10-28;}

    description
        "ocp-plugin-impl";

    revision "2015-08-11" {
        description
            "First ocp plugin implementation.";
    }

    identity ocp-plugin-provider-impl {
        base config:module-type;
        config:provided-service ocp-provider:ocp-provider;
        config:java-name-prefix OcpProvider;
    }

    augment "/config:modules/config:module/config:configuration" {
        case ocp-plugin-provider-impl {
            when "/config:modules/config:module/config:type = 'ocp-plugin-provider-impl'";

            container data-broker {
                uses config:service-ref {
                    refine type {
                        mandatory true;
                        config:required-identity md-sal-binding:binding-async-data-broker;
                    }
                }
            }
            container rpc-registry {
                uses config:service-ref {
                    refine type {
                        mandatory true;
                        config:required-identity md-sal-binding:binding-rpc-registry;
                    }
                }
            }
            container notification-adapter {
                uses config:service-ref {
                    refine type {
                        mandatory true;
                        config:required-identity sal-broker:binding-new-notification-service;
                    }
                }
            }
            container notification-publish-adapter {
                uses config:service-ref {
                    refine type {
                        mandatory true;
                        config:required-identity sal-broker:binding-new-notification-publish-service;
                    }
                }
            }
            list ocp-radiohead-connection-provider {
                uses config:service-ref {
                    refine type {
                        mandatory true;
                        config:required-identity ocp-radiohead-connection-provider:ocp-radiohead-connection-provider;
                    }
                }
            }
            leaf ocp-version {
                type string;
            }

            leaf rpc-requests-quota {
                type uint32;
                default 500;
            }
            leaf global-notification-quota {
                type uint32;
                default 131072;
            }
        }

    }
}
